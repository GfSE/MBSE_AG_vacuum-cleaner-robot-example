package <VRS> VacuumingRoboterSystem {
package <VRSRE> VRS_Requirements{
    //SysML kann hier nicht linken - tool abhängig
}
package <VRSC> VRS_Context;
package <VRSUC> VRS_UseCases;
package <VRSA> VRS_Actors;
package <VRSSA> VRS_SystemArchitecture;
}
